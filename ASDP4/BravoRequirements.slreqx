# BravoRequirements

## User Interface: Requirements focused on the UI/UX after drone deployment (Container)

### Direct Control: Operator can take direct control of a single drone with a controller. (Functional)
- Keywords: Customer, Functional

### Operational Complexity: Manual operation of drone should not be complex. (Functional)
- Keywords: Customer, Functional

### Data to Display: Drones must include battery life, flight stats, drone position, obstacle warning, battery warning indicators. (Functional)
- Keywords: Supplier, Functional

### UI Customization: UI of ground control should be highly customizable to present data for each drone and let user decide how data is displayed. (Functional)
- Keywords: Supplier, Functional

### Camera Display: Every drone should have its camera feed displayed at the ground station. (Functional)
- Keywords: Supplier, Functional

### Thermal Switch: Must have an option to switch between thermal and optical camera view. (Functional)
- Keywords: Supplier, Functional

## Control System: Requirements focused on the control system software used on the Ground Control station (Container)

### Position Designation: Operator must be able to designate positions for drones to manoeuvre to. (Functional)
- Keywords: Customer, Functional

### Recall Button: A “recall button” should be included to make all drones return to station on demand. (Functional)
- Keywords: Supplier, Functional

### GC Autonomy Handling: Ground station must handle all autonomous control (except object evasion for each unit) and transmit control signals to drones. (Functional)
- Keywords: Supplier, Performance

## Data Transmission: Requirements focused on the sending and recieving of data to and from the Ground Control station (Container)

### Seperate Communication: Ground station must be able to communicate to drones separately. (Functional)
- Keywords: Supplier, Functional

### Signal Decoding: Ground station must be able to encode and decode signals sent to and from drones respectively. (Functional)
- Keywords: Supplier, Functional

### Video Quality: The camera feed of the drone must be of sufficient quality for face recognition. (Functional)
- Keywords: Supplier, Performance

### Signal Power: Ground Control must have a strong R/T setup to receive and transmit data in long distances through concrete structures. (Functional)
- Keywords: Supplier, Reliability

### Data Encryption: Signals should be encrypted to prevent hacking/data leak . (Functional)
- Keywords: Supplier, Reliability

## Maintenance and Operation: Requirements focused on the upkeep of the system and deployment of the system (Container)

### System Size: All equipment must fit within and be operated from a standard police van (Functional)
- Keywords: Customer, Performance

### Software Upkeep: The drone control software can be easily maintained and is upgradeable. (Functional)
- Keywords: Supplier, Maintenability

### Hardware Upkeep: The hardware components of the ground control and drone should be cost-efficient to maintain. (Functional)
- Keywords: Supplier, Maintenability

### Setup Time: The equipment must have a quick setup time. (Functional)
- Keywords: Customer, Performance
